from FCUtil.block import *

def horizontal_dove_tail(gap=0,long_gap=None,back_gap=None,mirror=False,short=False,shallow=False):
  wt = 1.5
  slot_width = 3.0 #3.7 # 2.5 # mm
  if long_gap is None:
     long_gap = gap
  if back_gap is None:
     back_gap = gap
  hunit = 5*1.6
  vunit = 6*1.6
  if short:
     height = vunit
     ratio = 4/5.0
  else:
     height = 2*hunit
     ratio = 2/3.0
  ratio2 = 2/3.0
  if shallow:
     depth = hunit - (slot_width + (wt-1))
  else:
     depth = hunit
  b  = makeBox((hunit-2*(1+gap))*ratio, height-2*(1+long_gap), depth-(1+back_gap))
  b1 = makeBox((hunit-2*(1+gap))*ratio, (height-2*(1+long_gap))*ratio2, depth-(1+back_gap))
  b1.rotate(Base.Vector((hunit-2*(1+gap))*ratio,0,0),Base.Vector(0,0,1),-45)
  b = b.fuse(b1)
  b2 = makeBox((hunit-2*(1+gap))*ratio, (height-2*(1+long_gap))*ratio2, depth-(1+back_gap))
  b2.translate((0,(height-2*(1+long_gap))*(1-ratio2),0))
  b2.rotate(Base.Vector((hunit-2*(1+gap))*ratio,height-2*(1+long_gap),0),Base.Vector(0,0,1),45)
  b = b.fuse(b2)
  if not short:
     b3 = makeBox((hunit-2*(1+gap))*ratio, (height-2*(1+long_gap))*.7, depth-(1+back_gap))
     b3.rotate(Base.Vector((hunit-2*(1+gap))*ratio,0,0),Base.Vector(0,0,1),-22)
     b = b.fuse(b3)
  b4 = makeBox((hunit-2*(1+gap))*2, (height-2*(1+long_gap)), hunit-(1+back_gap))
  b4.translate((hunit-(1+back_gap),0,0))
  b = b.cut(b4)
  b.translate((1+gap,1+long_gap,vunit-depth+(1+back_gap)))
  if mirror:
    b = b.mirror(Base.Vector(hunit/2.0,0,0),Base.Vector(1,0,0))
  return b
    
def horizontal_dove_tail_hole(gap=0, long_gap=None,back_gap=None,mirror=False,short=False,shallow=False,shrink_depth=False):
  wt = 1.5
  slot_width = 3.0 #3.7 # 2.5 # mm
  vunit = 6*1.6
  hunit = 5*1.6
  b = myblock(1,2,1,has_under_tubes=False,bottom_play=0.0,horizontal_play=0.0,solid=True,has_knobs=False)
  hole = horizontal_dove_tail(gap, long_gap, back_gap, short=short,shallow=shallow)
  b = b.cut(hole)
  if shrink_depth:
     c = makeBox(hunit*2, hunit*4, (slot_width+(wt-1))+vunit-hunit)
     c.translate((-hunit,-hunit*2,0))
     b = b.cut(c)
  if mirror:
    b = b.mirror(Base.Vector(hunit/2.0,0,0),Base.Vector(1,0,0))
  return b
  
def vertical_dove_tail(gap=0, long_gap=None, back_gap=None, mirror=False, short=False,shallow=False):
  vunit = 6*1.6
  hunit = 5*1.6
  hole = horizontal_dove_tail(gap, long_gap, back_gap, short=short,shallow=shallow)
  hole.translate((0,0,hunit-vunit))
  hole.rotate(Base.Vector(0,0,0),Base.Vector(1,0,0),90)
  hole.translate((0,hunit,0))
  b = hole
  if mirror:
    b = b.mirror(Base.Vector(hunit/2.0,0,0),Base.Vector(1,0,0))
  return b

def vertical_dove_tail_hole(gap=0, long_gap=None, back_gap=None, mirror=False, short=False, has_knob=False,shallow=False,shrink_depth=False,shrink_height=False):
  wt = 1.5
  slot_width = 3.0 #3.7 # 2.5 # mm
  vunit = 6*1.6
  hunit = 5*1.6
  if short:
    vsize = 1
  else:
    vsize = 2
  b = myblock(1,1,vsize,has_under_tubes=False,bottom_play=0.0,horizontal_play=0.0,solid=True,has_knobs=has_knob)
  hole = horizontal_dove_tail(gap, long_gap, back_gap, short=short,shallow=shallow)
  hole.translate((0,0,hunit-vunit))
  hole.rotate(Base.Vector(0,0,0),Base.Vector(1,0,0),90)
  hole.translate((0,hunit,0))
  b = b.cut(hole)
  if shrink_depth:
     c = makeBox(hunit*2, (slot_width+(wt-1)), vunit*2)
     c.translate((-hunit,hunit-(slot_width+(wt-1)),-vunit))
     b = b.cut(c)
  if shrink_height and vsize==2:
     c = makeBox(hunit*2, hunit*2, vunit)
     c.translate((-hunit,-hunit,hunit*2))
     b = b.cut(c)
  if mirror:
    b = b.mirror(Base.Vector(hunit/2.0,0,0),Base.Vector(1,0,0))
  return b

def joiner():
  units = 1.6
  knob_diameter = 3.0 * units + 0.05 # "loose"
  knob_height = 1.0 * units  + 0.2
  hunit = 5*1.6
  vunit = 6*1.6
  b = horizontal_dove_tail(mirror=True)
  b.translate((0,hunit,0))
  b1 = makeBox(hunit*3-4, 3*hunit-4, (hunit-1)-(vunit/3.0)-.1)
  b1.translate((-3*hunit+4,0,vunit-hunit+1))
  b = b.fuse(b1)
  b2 = horizontal_dove_tail(mirror=False)
  b2.translate((0,hunit,0))
  b2.rotate(Base.Vector(0,0,0),Base.Vector(0,0,1),90)
  b2.translate((0,-hunit,0))
  b = b.fuse(b2)
  corner = makeBox((hunit*3-4)*2, 3*hunit-4, (hunit-1)-(vunit/3.0)-.1)
  corner.rotate(Base.Vector(0,0,0),Base.Vector(0,0,1),45)
  corner.translate((-3*hunit+4,0,vunit-hunit+1))
  b = b.cut(corner)

  knob1 = makeCylinder(knob_diameter/2.0,knob_height)
  knob1.translate((0.5*hunit,1.5*hunit,vunit))
  b = b.fuse(knob1)
  knob2 = makeCylinder(knob_diameter/2.0,knob_height)
  knob2.translate((0.5*hunit,2.5*hunit,vunit))
  b = b.fuse(knob2)
  knob3 = makeCylinder(knob_diameter/2.0,knob_height)
  knob3.translate((-2.5*hunit,-hunit/2.0,vunit))
  b = b.fuse(knob3)
  knob4 = makeCylinder(knob_diameter/2.0,knob_height)
  knob4.translate((-1.5*hunit,-hunit/2.0,vunit))
  b = b.fuse(knob4)
  
  b.translate((0,0,vunit))
  return b

def box_corner(height):
  hunit = 5*1.6
  vunit = 6*1.6
  slot_width = 3.0 #3.7 # 2.5 # mm
  slot_depth = 0.7*vunit
  wt = 1.5
  
  # Dove tails
  b = vertical_dove_tail()
  b.rotate(Base.Vector(0,0,0),Base.Vector(0,0,1),-90)
  b.translate((0,hunit,0))
  b1 = myblock(1,1,1,has_under_tubes=False,bottom_play=0.0,horizontal_play=0.0,solid=True,has_knobs=False)
  b1.translate((0,-hunit,0))
  b = b.fuse(b1)
  b2 = vertical_dove_tail()
  b2 = b2.mirror(Base.Vector(0,hunit/2.0,0),Base.Vector(0,1,0))
  b2.translate((-hunit,-hunit,0))
  b = b.fuse(b2)

  # bottom layer
  b3  = myblock(2,2,1,has_under_tubes=False,has_horizontal_holes=False,bottom_play=0.0,horizontal_play=0.0,solid=False,has_knobs=False,
                top_thickness=1.1+slot_width,has_struts=0,strut_sides=1)
  b3.translate((0,-2*hunit,-vunit))
  b = b.fuse(b3)
  slot = makeBox(slot_depth,slot_depth,slot_width)
  slot.translate((0,-slot_depth,-slot_width))
  b = b.cut(slot)
  
  # Outside wall of slot
  b4 = makeBox(wt,2*hunit,slot_depth)
  b4.translate((2*hunit-wt,-2*hunit,0*vunit))
  b = b.fuse(b4)
  b4a = makeBox(2*hunit,wt,slot_depth)
  b4a.translate((0,-2*hunit,0*vunit))
  b = b.fuse(b4a)

  # Inside wall of slot
  b5 = makeBox(wt,2*hunit-slot_width-wt,2.5+vunit) #slot_depth)
  b5.translate((2*hunit-2.0*wt-slot_width,-2*hunit+slot_width+wt,0*vunit))
  b = b.fuse(b5)
  b5a = makeBox(2*hunit-slot_width-wt,wt,2.5+vunit) #slot_depth)
  b5a.translate((0,-2*hunit+slot_width+wt,0*vunit))
  b = b.fuse(b5a)

  # Joining holes
  b6 = myblock(1,1,1,has_under_tubes=False,has_horizontal_holes=True,bottom_play=0.0,horizontal_play=0.0,solid=True,has_knobs=False,
               horizontal_hole_offset=0.5*hunit,has_keystone=False)
  b6.translate((hunit,-1*hunit,0))
  #b = b.fuse(b6)
  b6a = myblock(1,1,1,has_under_tubes=False,has_horizontal_holes=True,bottom_play=0.0,horizontal_play=0.0,solid=True,has_knobs=False,
               horizontal_hole_offset=0.5*hunit, keystone_angle=-90)
  b6a.rotate(Base.Vector(0,0,0),Base.Vector(0,0,1),90)
  b6a.translate((hunit*1,-2*hunit,0))
  #b = b.fuse(b6a)

  # Corner
  b7 = myblock(1,1,1,has_under_tubes=False,has_horizontal_holes=False,bottom_play=0.0,horizontal_play=0.0,solid=True,has_knobs=False)
  b7.translate((hunit,-2*hunit,0))
  #b = b.fuse(b7)

  # Fill
  b8 = makeBox(2*hunit-slot_width-2*wt,2*hunit-slot_width-2*wt,2.5+vunit)
  b8.translate((0,-2*hunit+slot_width+2*wt,0*vunit))
  b = b.fuse(b8)

  # column
  col_height = vunit*(height-2)
  b9 = makeBox(slot_width+2*wt,slot_width+2*wt,col_height)
  b9.translate((2*hunit-(slot_width+2*wt),-2*hunit,0*vunit))
  b = b.fuse(b9)

  # bottom vertical slot sides
  slot_depth_side = 2*hunit-(slot_width+2*wt)
  b10 = makeBox(wt,slot_depth_side,col_height-vunit)
  b10.translate((2*hunit-wt,-2*hunit+(slot_width+2*wt),0*vunit))
  b = b.fuse(b10)
  b10a = makeBox(wt,slot_depth_side,col_height-vunit)
  b10a.translate((2*hunit-2*wt-slot_width,-2*hunit+(slot_width+2*wt),0*vunit))
  b = b.fuse(b10a)
  b10b = makeBox(slot_depth_side,wt,col_height-vunit)
  b10b.translate((2*hunit-2*wt-slot_width-slot_depth_side,-2*hunit+(slot_width+wt),0*vunit))
  b = b.fuse(b10b)
  b10c = makeBox(slot_depth_side,wt,col_height-vunit)
  b10c.translate((2*hunit-2*wt-slot_width-slot_depth_side,-2*hunit,0*vunit))
  b = b.fuse(b10c)

  b.translate((0,2*hunit,vunit))

  # top dovetails (big)
  b11 = vertical_dove_tail(short=False, shallow=True)
  b11.rotate(Base.Vector(0,0,0),Base.Vector(0,0,1),-90)
  b11.translate((0,3*hunit,(height-2)*vunit))
  b = b.fuse(b11)
  b12 = vertical_dove_tail(short=False, shallow=True, mirror=True)
  b12.rotate(Base.Vector(0,0,0),Base.Vector(0,0,1),180)
  b12.translate((0,2*hunit,(height-2)*vunit))
  b = b.fuse(b12)

  # top dovetails (small)
  b11 = vertical_dove_tail(short=True, shallow=True)
  b11.rotate(Base.Vector(0,0,0),Base.Vector(0,0,1),-90)
  b11.translate((hunit,2*hunit,(height-1)*vunit))
  b = b.fuse(b11)
  b12 = vertical_dove_tail(short=True, shallow=True, mirror=True)
  b12.rotate(Base.Vector(0,0,0),Base.Vector(0,0,1),180)
  b12.translate((hunit,1*hunit,(height-1)*vunit))
  b = b.fuse(b12)

  # top level
  b13 = myblock(1,1,2,has_under_tubes=False,bottom_play=0.0,horizontal_play=0.0,solid=True,has_knobs=False)
  b13.translate((0,hunit,(height-2)*vunit))
  b = b.fuse(b13)
  b14 = myblock(1,1,2,has_under_tubes=False,bottom_play=0.0,horizontal_play=0.0,solid=True,has_knobs=False)
  b14.translate((hunit,0,(height-2)*vunit))
  b = b.fuse(b14)

  # Fill
  b8a = makeBox(2*hunit-slot_width-1*wt,2*hunit-slot_width-1*wt,1)
  b8a.translate((0,0*hunit+slot_width+1*wt,(height-2)*vunit-1))
  b = b.fuse(b8a)

# top joining holes
  b15 = myblock(1,1,1,has_under_tubes=False,has_horizontal_holes=True,bottom_play=0.0,horizontal_play=0.0,solid=True,has_knobs=False,
               horizontal_hole_offset=0.5*hunit,has_keystone=False)
  b15.rotate(Base.Vector(0,0,0),Base.Vector(0,0,1),180)
  b15.translate((hunit*2,hunit*2,(height-1)*vunit))
  #b = b.fuse(b15)
  b16 = myblock(1,1,1,has_under_tubes=False,has_horizontal_holes=True,bottom_play=0.0,horizontal_play=0.0,solid=True,has_knobs=False,
               horizontal_hole_offset=0.5*hunit, keystone_angle=-90)
  b16.rotate(Base.Vector(0,0,0),Base.Vector(0,0,1),90)
  b16.translate((hunit,0,(height-1)*vunit))
  #b = b.fuse(b16)
  
  # top vertical slot sides
  b17 = makeBox(wt,slot_depth+hunit,slot_depth)
  b17.translate((2*hunit-wt,hunit,(height-1)*vunit-slot_depth))
  #b = b.fuse(b17)
  b18 = makeBox(wt,slot_depth+hunit,slot_depth)
  b18.translate((2*hunit-wt-slot_width-wt,hunit,(height-1)*vunit-slot_depth))
  #b = b.fuse(b18)
  b19 = makeBox(slot_depth+hunit,wt,slot_depth)
  b19.translate((-slot_depth,0,(height-1)*vunit-slot_depth))
  #b = b.fuse(b19)
  b20 = makeBox(slot_depth+hunit,wt,slot_depth)
  b20.translate((-slot_depth,slot_width+wt,(height-1)*vunit-slot_depth))
  #b = b.fuse(b20)

  test = makeBox(hunit*5,hunit*5,vunit*3)
  #test.translate((-hunit,-hunit,0))
  test.translate((-hunit,-hunit,3*vunit))
  #b = b.cut(test)
  return b
  
def box_side_bottom(length):
  wt = 1.5
  hunit = 5*1.6
  vunit = 6*1.6
  slot_width = 3.0 # 3.7 # 2.5 # mm
  slot_depth = 0.7*vunit
  vgap=0
  v_long_gap = .2 # .1 works tight
  v_back_gap = 0.1
  # test
  #b = vertical_dove_tail(1,2)
  #b1 = vertical_dove_tail_hole()
  #b = b.fuse(b1)
  #return b
  # end test
  
  # near dovetails
  b = vertical_dove_tail_hole(-vgap, -v_long_gap, -v_back_gap,shrink_height=True) # slightly bigger
  b.rotate(Base.Vector(0,0,0),Base.Vector(0,0,1),-90)
  b.translate((0,hunit,0))
  b1 = horizontal_dove_tail_hole(mirror=True)
  b1.translate((0,hunit,0))
  b = b.fuse(b1)

  # test
  #b5 = vertical_dove_tail()
  #b5.rotate(Base.Vector(0,0,0),Base.Vector(0,0,1),-90)
  #b5.translate((0,hunit,0))
  #b = b.fuse(b5)
  #b6 = makeBox(hunit*1, 2*hunit, vunit)
  #b6.translate((0,1.5*hunit,0))
  #b = b.cut(b6)
  #return b
  # end test
  
  # bottom layer
  b2  = myblock(2,length,1,has_under_tubes=True,has_horizontal_holes=False,bottom_play=0.0,horizontal_play=0.0,solid=False,has_knobs=False,
                top_thickness=1.1+slot_width,has_struts=0,strut_sides=1,loose=True)
  b2.rotate(Base.Vector(0,0,0), Base.Vector(0,0,1), 180)
  b2.translate((2*hunit,length*hunit,-vunit))
  b = b.fuse(b2)

  # Slot in the bottom layer
  slot = makeBox(slot_depth,hunit*length,slot_width)
  slot.translate((0,0,-slot_width))
  b = b.cut(slot)

  # Top of slot
  b3 = makeBox(hunit*2-2*wt-slot_width,hunit*length,1.0)
  b = b.fuse(b3)

  # Outside wall of slot
  b4 = makeBox(wt,hunit*(length),slot_depth)
  b4.translate((2*hunit-wt,0,0))
  b = b.fuse(b4)
  b4a = makeBox(wt,slot_depth,vunit+slot_depth)
  b4a.translate((2*hunit-wt,0,0))
  #b = b.fuse(b4a)
  b4a1 = makeBox(wt,slot_depth,vunit+slot_depth)
  b4a1.translate((2*hunit-wt,hunit*length-slot_depth,0))
  #b = b.fuse(b4a1)

  # Inside wall of slot
  b5 = makeBox(wt,hunit*(length),slot_depth)
  b5.translate((2*hunit-2.0*wt-slot_width,0,0))
  b = b.fuse(b5)
  b5a = makeBox(wt,slot_depth,slot_depth+vunit)
  b5a.translate((2*hunit-2.0*wt-slot_width,0,0))
  #b = b.fuse(b5a)
  b5a1 = makeBox(wt,slot_depth,slot_depth+vunit)
  b5a1.translate((2*hunit-2.0*wt-slot_width,hunit*length-slot_depth,0))
  #b = b.fuse(b5a1)

  # far dovetails
  b6 = vertical_dove_tail_hole(-vgap, -v_long_gap, -v_back_gap, mirror=True,shrink_height=True) # slightly bigger
  b6.rotate(Base.Vector(hunit/2.0,hunit/2.0,0),Base.Vector(0,0,1),-90)
  b6.translate((0,hunit*(length-1),0))
  b = b.fuse(b6)
  b7 = horizontal_dove_tail_hole(mirror=True)
  b7.translate((0,hunit*(length-3),0))
  b = b.fuse(b7)
  
  # slot reinforcement
  b8 = makeBox(hunit-2-slot_width,1,slot_depth)
  b8.translate((hunit,0,0))
  b = b.fuse(b8)
  b8a = makeBox(hunit-2-slot_width,1,slot_depth)
  b8a.translate((hunit,hunit*3-1,0))
  b = b.fuse(b8a)
  b8b = makeBox(hunit-2-slot_width,1,slot_depth)
  b8b.translate((hunit,hunit*(length-3),0))
  b = b.fuse(b8b)
  b8c = makeBox(hunit-2-slot_width,1,slot_depth)
  b8c.translate((hunit,hunit*(length)-1,0))
  b = b.fuse(b8c)

  # Clip everything outside off the play boundary
  play_boundary = makeBox(
    hunit*2-2*0.1,
    hunit*length-2*0.1,
    vunit*2+slot_depth) # extra vunit for knobs
#   vunit*3-0.1 + vunit) # extra vunit for knobs
  play_boundary.translate((
    0.1,
    0.1,
    0.1-vunit))
  b = b.common(play_boundary)
  
  b.translate((0,0,vunit))

  return b

def box_side_top(length):
  wt = 1.5
  hunit = 5*1.6
  vunit = 6*1.6
  slot_width = 3.0 # 3.7 # 2.5 # mm
  slot_depth = 0.7*vunit
  vgap=0
  v_long_gap = .2 # .1 works tight
  v_back_gap = 0.1
  top_thickness = 1.1
  
  # near dovetails
  b = vertical_dove_tail_hole(-vgap, -v_long_gap, -v_back_gap, short=False, has_knob=True,shallow=True)
  b.rotate(Base.Vector(0,0,0),Base.Vector(0,0,1),-90)
  b.translate((0,hunit,0))
  b1 = horizontal_dove_tail_hole(mirror=True,shallow=False)
  b1.translate((0,hunit,vunit))
  b = b.fuse(b1)

  # far dovetails
  b4 = vertical_dove_tail_hole(-vgap, -v_long_gap, -v_back_gap, short=False, has_knob=True,shallow=True,mirror=True)
  b4.rotate(Base.Vector(0,0,0),Base.Vector(0,0,1),-90)
  b4.translate((0,hunit*(length),0))
  b = b.fuse(b4)
  b5 = horizontal_dove_tail_hole(mirror=True,shallow=False)
  b5.translate((0,hunit*(length-3),vunit))
  b = b.fuse(b5)
  
  # 2x1's under dovetails
  b8  = myblock(1,2,1,has_under_tubes=False,has_horizontal_holes=False,bottom_play=0.0,horizontal_play=0.0,solid=False,has_knobs=False,
                has_struts=0,strut_sides=1,loose=True)
  b8.translate((0,hunit,0*vunit))
  b = b.fuse(b8)
  b9  = myblock(1,2,1,has_under_tubes=False,has_horizontal_holes=False,bottom_play=0.0,horizontal_play=0.0,solid=False,has_knobs=False,
                has_struts=0,strut_sides=1,loose=True)
  b9.translate((0,hunit*(length-3),0*vunit))
  b = b.fuse(b9)

  # 1x1's on end
  b10  = myblock(1,1,1,has_under_tubes=False,has_horizontal_holes=False,bottom_play=0.0,horizontal_play=0.0,solid=True,has_knobs=False,
                has_struts=0,strut_sides=1,loose=True)
  b10.translate((1*hunit,-1*hunit,0*vunit))
  b = b.fuse(b10)
  b11  = myblock(1,1,1,has_under_tubes=False,has_horizontal_holes=False,bottom_play=0.0,horizontal_play=0.0,solid=True,has_knobs=False,
                has_struts=0,strut_sides=1,loose=True)
  b11.translate((1*hunit,(length)*hunit,0*vunit))
  b = b.fuse(b11)

  # 1x1 dovetails
  b12 = vertical_dove_tail_hole(-vgap, -v_long_gap, -v_back_gap, short=True, has_knob=True,shallow=True)
  b12.rotate(Base.Vector(0,0,0),Base.Vector(0,0,1),-90)
  b12.translate((hunit,0*hunit,vunit))
  b = b.fuse(b12)
  b13 = vertical_dove_tail_hole(-vgap, -v_long_gap, -v_back_gap, short=True, has_knob=True,shallow=True,mirror=True)
  b13.rotate(Base.Vector(0,0,0),Base.Vector(0,0,1),-90)
  b13.translate((hunit,(length+1)*hunit,vunit))
  b = b.fuse(b13)
  
  # middle
  b2  = myblock(2,length-6,2,has_under_tubes=False,has_horizontal_holes=False,bottom_play=0.0,horizontal_play=0.0,solid=True,has_knobs=True,
                has_struts=0,strut_sides=1,loose=True)
  b2.rotate(Base.Vector(0,0,0), Base.Vector(0,0,1), 180)
  b2.translate((2*hunit,(length-3)*hunit,0))
  b = b.fuse(b2)

  # 1x3's
  b3  = myblock(1,3,2,has_under_tubes=False,has_horizontal_holes=False,bottom_play=0.0,horizontal_play=0.0,solid=True,has_knobs=True,
                has_struts=0,strut_sides=1,loose=True)
  b3.translate((hunit,0,0))
  b = b.fuse(b3)
  b6  = myblock(1,3,2,has_under_tubes=False,has_horizontal_holes=False,bottom_play=0.0,horizontal_play=0.0,solid=True,has_knobs=True,
                has_struts=0,strut_sides=1,loose=True)
  b6.translate((hunit,hunit*(length-3),0))
  b = b.fuse(b6)

  # clear out underside for side
  b7 = makeBox(hunit-wt,hunit*(length+2)-4*wt,vunit-top_thickness)
  b7.translate((hunit,-hunit+2*wt,0))
  b = b.cut(b7)
  b14 = makeBox(2*hunit-wt*2,hunit*(length-2)-2*wt,vunit-top_thickness)
  b14.translate((0*hunit+wt,hunit+wt,0))
  #b = b.cut(b14)
  b14a = makeBox(hunit-wt*2,hunit*(length-2)-2*wt,vunit-top_thickness)
  b14a.translate((0*hunit+wt,hunit+wt,0))
  b = b.cut(b14a)

  # Extra thin edge
  b15 = makeBox(wt,hunit-wt,vunit)
  b15.translate((1*hunit-wt,-1*hunit+wt,0))
  #b = b.fuse(b15)
  b16 = makeBox(wt,hunit-wt,vunit)
  b16.translate((1*hunit-wt,(length)*hunit,0))
  #b = b.fuse(b16)
  
  # Clip everything outside off the play boundary
  play_boundary = makeBox(
    hunit*2-2*0.1,
    hunit*(length+2)-2*0.1,
    vunit*3) # extra vunit for knobs
  play_boundary.translate((
    0.1,
    -hunit+0.1,
    0.1))
  #b = b.common(play_boundary)

  return b
  
#b = block(2,2,1/3.0,top_thickness=-0.02,unit=1.6*2))
#b = block(2,2,1/3.0,has_ridges=False) # block4
#b = block(2,2,1/3.0,has_ridges=False,has_under_tube_cavities=False) # block5
#b = block(2,2,1/3.0,has_ridges=False,has_under_tubes=False,has_knobs=False) # block6
#b = block(2,2,1/3.0,wall_thickness=1.4,has_ridges=False,has_under_tubes=False,has_knobs=False) # block7
#b = block(2,2,1/3.0,wall_thickness=1.45,has_ridges=False,has_under_tubes=False,has_knobs=False) # block8
#b = block(2,2,1,wall_thickness=1.45,has_ridges=False,under_tube_outer_diameter=(5*sqrt(2)-3)*(1.6)+0.05,
#          bottom_play=0.1) # block9
#b = block(2,8,1/3.0,wall_thickness=1.45,has_ridges=False,under_tube_outer_diameter=(5*sqrt(2)-3)*(1.6)+0.05,
#          bottom_play=0.1) # block10

#b = tube(2,2,1,has_under_tube_cavities=False) # tube1
#b = tube(2,2,1,has_under_tube_cavities=False,under_tube_outer_diameter = (5*sqrt(2)-3)*(1.6) - 0.1 +0.05) # tube2
#b = tube(2,2,1,has_under_tube_cavities=True,under_tube_outer_diameter = (5*sqrt(2)-3)*(1.6) - 0.1 +0.05) # tube3
#b = tube(2,2,1,has_under_tube_cavities=False,under_tube_outer_diameter = (5*sqrt(2)-3)*(1.6)) # tube4
#b = tube(2,2,1,has_under_tube_cavities=True,under_tube_outer_diameter = (5*sqrt(2)-3)*(1.6)) # tube5
#b = tube(2,2,1,has_under_tube_cavities=False,under_tube_outer_diameter = (5*sqrt(2)-3)*(1.6)+0.05) # tube6
#b = tube(2,2,1,has_under_tube_cavities=True,under_tube_outer_diameter = (5*sqrt(2)-3)*(1.6)+0.05) # tube7
#b = tube(2,2,1,has_under_tube_cavities=False,under_tube_outer_diameter = (5*sqrt(2)-3)*(1.6)+0.10) # tube8
#b = tube(2,2,1,has_under_tube_cavities=True,under_tube_outer_diameter = (5*sqrt(2)-3)*(1.6)+0.10) # tube9
#b = block(2,2,1,has_ridges=False,under_tube_outer_diameter=(5*sqrt(2)-3)*(1.6)+0.1,
#          bottom_play=0.1,knob_diameter=3.0*1.6 + 0.20) # block11
#b = block(2,2,1/3.0,has_ridges=False,under_tube_outer_diameter=(5*sqrt(2)-3)*(1.6)+0.1,
#          bottom_play=0.1,knob_diameter=3.0*1.6 + 0.15) # block12
#b = block(2,2,1,has_ridges=False,under_tube_outer_diameter=(5*sqrt(2)-3)*(1.6)+0.1,
#          bottom_play=0.1,knob_diameter=3.0*1.6 + 0.15) # block13
#b = block(2,6,1/3.0,has_ridges=False,under_tube_outer_diameter=(5*sqrt(2)-3)*(1.6)+0.1,
#          bottom_play=0.1,knob_diameter=3.0*1.6 + 0.15,has_vertical_holes=1) # block14
#b = block(2,4,1,has_ridges=False,under_tube_outer_diameter=(5*sqrt(2)-3)*(1.6)+0.1,
#          bottom_play=0.1,knob_diameter=3.0*1.6 + 0.15) # block15
#b = block(2,6,1/3.0,has_ridges=False,under_tube_outer_diameter=(5*sqrt(2)-3)*(1.6)+0.1,
#          bottom_play=0.1,knob_diameter=3.0*1.6 + 0.15) # block16
#b = block(1,2,1.0,has_ridges=False,has_under_tubes=False, knob_diameter=3.0*1.6 + 0.15,
#          bottom_play=0.1, has_horizontal_holes=True) # block17
#b = block(1,2,1.0,has_ridges=False,has_under_tubes=False, knob_diameter=3.0*1.6 + 0.15,
#          bottom_play=0.1, has_horizontal_holes=True, horizontal_hole_diameter=3.0 * 1.6 + 0.05 * mm, has_knobs=False) # block18
#b = block(1,2,1.0,has_ridges=False,has_under_tubes=False, knob_diameter=3.0*1.6 + 0.15,
#          bottom_play=0.1, has_horizontal_holes=True, horizontal_hole_diameter=3.0 * 1.6) # block19

if False:
  b = box_corner()
  show(b)
   
  b2 = box_corner()
  b2.rotate(Base.Vector(0,0,0), Base.Vector(0,0,1), -180)
  b2.translate((-0.3, 2*5*1.6, 0))
  show(b2)
   
  bridge = makeBox(2.0, 2*5*1.6-2*.1, 0.150)
  bridge.translate((-1.0, 0.1, 0))
  show(bridge)

# box_side_bottom_with_support
if False:
  hunit = 5*1.6
  vunit = 6*1.6
  slot_depth = 0.7*vunit
  b = box_side_bottom_old1(12)
  top_b, bottom_b = vsplit(b, -2.5)
  bridge = makeBox(2.2+.1+slot_depth, 12*hunit, 0.150)
  bridge.translate((-2.2, 0, 0))
  support = makeBox(1.2, 12*hunit, vunit-.1)
  support.translate((-2.2,0,-vunit+.1))
  support = support.fuse(bridge)
  top_b = top_b.fuse(support)
  show(top_b)
  show(bottom_b)
  #show(support)

# assembled box
if True:
  hunit = 5*1.6
  vunit = 6*1.6
  b = box_side_bottom(12) # 12 28
  #top_b, bottom_b = vsplit(b, -2.5)
  #show(top_b)
  #show(bottom_b)
  show(b)
  #j = joiner()
  #show(j)
  c = box_corner(5) # 16 5
  c.translate((0,-2*hunit,0))
  #c.rotate(Base.Vector(0,0,0), Base.Vector(0,1,0), 90)
  show(c)
  t = box_side_top(12) # 12 28
  t.translate((0,0,vunit*3))
  show(t)
  
if False:
  b = box_side_top(12)
  show(b)
  
if False:
  b = myblock(2,6,1,has_struts=1,strut_sides=1)
  show(b)
